gsrWeatherStation DEFINITIONS::= BEGIN 

--IMPORTS MODULE-IDENTITY, OBJECT-TYPE, INTEGER32, enterprises FROM SNMPv2-SMI
IMPORT OBJECT-TYPE, NOTIFICATION-TYPE, MODULE-IDENTITY, Integer32, Opaque, enterprises, Counter32, Unsigned32 FROM SNMPv2-SMI
gsr MODULE-IDENTITY
     LAST-UPDATED "201704200000Z"
     ORGANIZATION "ESTIG-IPB"
     CONTACT-INFO
        "System And Network Management
		Head: José Borges
        Email: a39041@alunos.ipb.pt"

     DESCRIPTION
        "IPB's meteorological Weather Station for GSR"

  ::= { enterprises 12499 }

enterprises OBJECT IDENTIFIER ::= { internet .1.3.6.1.4.1 enterprises 12499}

-- 1.3.6.1.4.1
gsrWeatherSensor OBJECT IDENTIFIER ::= { gsr 1 }

--1.3.6.1.4.1.12499.1, identifica o sensor de vento
windSensor OBJECT IDENTIFIER ::= { gsrWeatherSensor 1 }
--1.3.6.1.4.1.12499.1.1 dentro do sensor de vento identifica a medicao do vento
--gsrWindGauge OBJECT IDENTIFIER ::= { windSensor 1 }
--1.3.6.1.4.1.12499.1.2 dentro do sensor do vento identifica a direcao do vento
--gsrWindDirection OBJECT IDENTIFIER ::= { windSensor 2 }


gsrWindGauge OBJECT TYPE 
	SYNTAX INTEGER
	UNITS "m/s"
	MAX-ACCESS read-only
	STATUS current
	DESCRIPTION "Sensor medidor do vento em velocidade, medida em graus"
::= { windSensor 1 }

gsrWindDirection OBJECT TYPE 
	SYNTAX INTEGER (0..360)
	UNITS "degree"
	MAX-ACCESS read-only
	STATUS current
	DESCRIPTION "Wind direction in degrees"
::= { windSensor 2 }
	
END gsrWeatherStation;
